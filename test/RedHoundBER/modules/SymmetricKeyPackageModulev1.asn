SymmetricKeyPackageModulev1
     { iso(1) member-body(2) us(840) rsadsi(113549) pkcs(1) pkcs-9(9)
       smime(16) modules(0) id-mod-symmetricKeyPkgV1(33) }

   DEFINITIONS IMPLICIT TAGS ::=

   BEGIN

   -- EXPORTS ALL

   IMPORTS

   -- From New PKIX ASN.1 [RFC5912]

   ATTRIBUTE
     FROM PKIX-CommonTypes-2009
      { iso(1) identified-organization(3) dod(6) internet(1)
        security(5) mechanisms(5) pkix(7) id-mod(0)
        id-mod-pkixCommon-02(57) }

   -- From New SMIME ASN.1 [RFC5911]

   CONTENT-TYPE, Attribute{}
     FROM CryptographicMessageSyntax-2010
       { iso(1) member-body(2) us(840) rsadsi(113549)
         pkcs(1) pkcs-9(9) smime(16) modules(0) id-mod-cms-2009(58) }

   ;

    ContentSet CONTENT-TYPE ::= {
       ct-symmetric-key-package,
       ... -- Expect additional content types --
     }

     ct-symmetric-key-package CONTENT-TYPE ::=
       { TYPE SymmetricKeyPackage IDENTIFIED BY id-ct-KP-sKeyPackage }

     id-ct-KP-sKeyPackage OBJECT IDENTIFIER ::=
       { iso(1) member-body(2) us(840) rsadsi(113549) pkcs(1) pkcs-9(9)
         smime(16) id-ct(1) 25 }

     SymmetricKeyPackage ::= SEQUENCE {
       version           KeyPkgVersion DEFAULT v1,
       sKeyPkgAttrs  [0] SEQUENCE SIZE (1..MAX) OF Attribute
                                      {{ SKeyPkgAttributes }} OPTIONAL,
       sKeys             SymmetricKeys,
       ... }

     SymmetricKeys ::= SEQUENCE SIZE (1..MAX) OF OneSymmetricKey

     OneSymmetricKey ::= SEQUENCE {
       sKeyAttrs  SEQUENCE SIZE (1..MAX) OF Attribute
                                         {{ SKeyAttributes }} OPTIONAL,
       sKey       OCTET STRING OPTIONAL }
       ( WITH COMPONENTS { ..., sKeyAttrs PRESENT } |
         WITH COMPONENTS { ..., sKey PRESENT } )

     KeyPkgVersion ::= INTEGER  { v1(1) } ( v1, ... )

     SKeyPkgAttributes ATTRIBUTE ::= { ... }

     SKeyAttributes ATTRIBUTE ::= { ... }

   END
